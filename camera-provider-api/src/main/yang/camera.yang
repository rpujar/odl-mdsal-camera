//This file contains a YANG data definition. This data model defines
  //a toaster, which is based on the SNMP MIB Toaster example 
  module camera {

    //The yang version - today only 1 version exists. If omitted defaults to 1.
    yang-version 1; 

    //a unique namespace for this module, to uniquely identify it from other modules that may have the same name.
    namespace "urn:opendaylight:params:xml:ns:yang:camera";

    //a shorter prefix that represents the namespace for references used below
    prefix camera;

    //defines the dates of revisions for this yang file
    revision "2009-11-20" {
      description
        "Camera module in progress.";
    }

    //declares a base identity, in this case a base type for different types of photos.
    identity photo-type { //creates a Java base class
      description
        "Base for all photo types supported by the camera. New photo types not listed here nay be added in the future.";
    }

    //the below identity section is used to define globally unique identities
    identity color { //creates Java class that extends the base class generated by photo-type block
      base photo-type;       //logically extending the declared toast-type above.
      description "Color Photo.";  //free text description of this type.
    }

    identity black-and-white {
      base photo-type;
      description "Black & White photo.";
    }

    //defines a new "Type" string type which limits the length
    typedef DisplayString { //creates a class DisplayString, with displaystring class variable, length is not mapped 
      type string {
        length "0 .. 255";
      }
      description
        "YANG version of the SMIv2 DisplayString TEXTUAL-CONVENTION.";
      reference
        "RFC 2579, section 2.";

    }

    // This definition is the top-level configuration "item" that defines a camera. The "presence" flag connotes there
    // can only be one instance of a camera which, if present, indicates the service is available.
    container camera-params { //creates a Java interface with same name 
      presence
        "Indicates the camera service is available";
      description
        "Top-level container for all camera database objects.";

      //Note in these three attributes that config = false. This indicates that they are operational attributes.
      //all leaf are mapped to getter methods returning type in Camera Java interface
      leaf cameraManufacturer {
        type DisplayString;
        config false;
        mandatory true;
        description
          "The name of the camera's manufacturer. For instance, Canon.";
      }

      leaf cameraModelNumber {
        type DisplayString;
        config false;
        mandatory true;
        description
          "The name of the camera's model. For instance, Rebel T3i.";
      }
      //enum is mapped to Java enum with value as a variable
      leaf cameraStatus {
        type enumeration {
          enum "on" {
            value 1;
            description
              "The camera is on. Photo is being taken now.";
          }
          enum "off" {
            value 2;
            description
              "The camera is off. No photo is being made now.";
          }
        }
        config false;
        mandatory true;
        description
          "This variable indicates the current state of the camera.";
      }
      leaf brightnessFactor {
        type uint32 {
         range "1 .. 30";
         }
        config true;
        default '1';
        description "The brightnessFactor, multiplied with the exposure value to attain the required levels";
       }
    }  // container camera
    
    //This defines a Remote Procedure Call (rpc). RPC provide the ability to initiate an action
    //on the data model. In this case the initiating action takes two optional inputs (because default value is defined)
    
    rpc click-photo {
     description
       "Click a photo. A photo-done Notif will be sent when the photo capture is complete.
        An in-use error will be returned if photo is already being made.
        A resource-denied error will be returned if the camera service is disabled.";
     input {
      leaf exposure {
       type int32 {
        range "-3 .. 3";
        }
       default '0';
       description
         "This variable controls how bright the image. It should be on a scale of -3 to 3.
          Photos clicked at 3 generally is very bright; and if clicked at -3 is too dark.";
      }
        
      leaf photoType {
       type identityref {
        base camera:photo-type;
        }
       default 'color';
       description 
         "This variable informs the camera of the type of photo that is being taken.
          The camera uses this information, combined with exposure,
          to compute for how long the shutter must be open to achieve the required exposure.";
      }
     }
    } //rpc click-photo
    
    rpc cancel-photo {
     description
       "Stop taking photo, if any is being taken.
        A resource-denied error will be returned if the camera service is disabled.";
    } //rpc cancel-photo

    //PART 6: NOTIFs
    rpc restock-camera {
     description
       "Restock the camera with the amount of memory needed for the amount of photos specified.";
     input {
       leaf amountOfPhotosToStock {
         type uint32;
         description
            "Indicates the number of photos needed to be made available to be clicked.";
       }
     }
   }

   notification cameraOutOfPhotos {
     description
       "Indicates that the camera has run of memory for clicking photos.";
   }  // notification cameraOutOfPhotos
   

   notification cameraRestocked {
     description
       "Indicates that the camera has been restocked.";
     leaf numberOfPhotos {
       type uint32;
       description
         "Indicates the number of photos made available to be clicked";
     }
   }  // notification cameraRestocked
  }  // module camera
